# -*- coding: utf-8 -*-
#
# You have to select one or multiple solids and then you launch the macro.
# You'll have a window listing the solids. You can put the density of your
# material or choose in a huge list of predefined materials.
# If you know your densities in another unit system, I used FreeCAD convert
# system to propose differents units.
# You can also display where is the center of mass.
# An import button allows you to quickly load saved densities (even if it's
# not a .csv file from the macro, as soon as there is a column named "Density"
# it will be loaded.)
#
# Icons import.png, compute.png, save.png, material.png, and com.png are
# from https://www.freepik.com/.

from __future__ import division
from __future__ import unicode_literals

__Name__ = 'CenterOfMass'
__Comment__ = 'Computation of the center of mass for multiple solids'
__Author__ = 'schupin'
__Version__ = '0.4.2'
__Date__ = '2019-06-09'
__License__ = 'LGPL-3.0-or-later'
__Web__ = 'https://forum.freecadweb.org/viewtopic.php?f=24&t=31883'
__Wiki__ = 'https://www.freecadweb.org/wiki/Macro_CenterOfMass'
__Icon__ = 'https://www.freecadweb.org/wiki/images/d/d7/Centomass.png'
__Help__ = 'Select or more bodies and launch'
__Status__ = 'alpha'
__Requires__ = 'freecad 0.18'
__Communication__ = 'https://forum.freecadweb.org/viewtopic.php?p=265270#p265270'
__Files__ = 'CenterOfMass/Macro_CenterOfMass_import.png,CenterOfMass/Macro_CenterOfMass_compute.png,CenterOfMass/Macro_CenterOfMass_save.png,CenterOfMass/Macro_CenterOfMass_material.png,CenterOfMass/Macro_CenterOfMass_com.png,CenterOfMass/Macro_CenterOfMass_colorify.png'

#todo :
#   -dockable

import csv
import glob
import os
import math
import re

from PySide import QtCore, QtGui

import FreeCAD
import FreeCADGui
import DraftVecUtils
import Material
import MaterialEditor

import sys
if sys.version_info.major >= 3:
    unicode = str
else:
    reload(sys)
    sys.setdefaultencoding('utf8')

g_desktop_width  = QtGui.QDesktopWidget().screenGeometry().width()
g_desktop_height = QtGui.QDesktopWidget().screenGeometry().height()
g_win_width      = int(g_desktop_width  * 0.25)
g_win_height     = int(g_desktop_height * 0.5)
g_scroll_height  = int(g_win_height     * 0.58)
g_button_height  = int(g_win_height     * (1.0 - 0.6) / 3.0)
g_icon_size      = int(g_button_height  * 0.35)

# Find FreeCAD's root window
g_freecad_root_window = FreeCADGui.getMainWindow()

class CenterofmassWindow(QtGui.QMainWindow):

    def __init__(self):
        super(CenterofmassWindow, self).__init__()
        self.setWindowFlags(
                    QtCore.Qt.Window |
                    QtCore.Qt.CustomizeWindowHint |
                    QtCore.Qt.WindowTitleHint |
                    QtCore.Qt.WindowCloseButtonHint |
                    QtCore.Qt.WindowStaysOnTopHint
        )
        self.setWindowTitle('Center Of Mass v.' + __Version__ + ' (' + __Date__ + ')')

        self.child = CenterofmassWidget(self)
        self.setCentralWidget(self.child)          

        self.child.initUI(self)
        if self.child.startup_failed:
            self.destroy()
        else:
            self.setPosition(g_freecad_root_window)
            self.child.show()
            self.show()

    # Set a sensible default position for the window
    # With FreeCAD's default layout, this will be over the docking area
    # so it will not obscure the 3D view
    def setPosition(self, parent):
        geom = parent.geometry()
        xpos = geom.left() + 50
        ypos = geom.center().y() - g_win_height // 2
        self.setGeometry(xpos, ypos, g_win_width, g_win_height)

class MaterialWidget():
    def __init__(self, label, spin, combo, parent, material_database, solid, originColor):
        self.label = label
        self.spin = spin
        self.combo = combo
        self.parent = parent
        self.material_database = material_database
        self.solid = solid
        self.originColor = originColor

    def on_comboMaterial_Changed(self, txt):
        materialName = self.combo.currentText()
        previous_value = self.spin.value()
        materialDensity = convert_density(
            self.material_database.get(materialName, -10.0),
            self.parent.comboUnit.currentText()
        )
        if materialDensity < 0.0:
            self.spin.setValue(previous_value)
            self.combo.setCurrentIndex(0)
        else:
            self.spin.setValue(materialDensity)
            self.combo.setCurrentIndex(self.combo.findText(materialName))

    def on_densitySpinBox_valueChanged(self, density):
        self.combo.setCurrentIndex(0)
        self.parent.on_pushButton_ComputeCDG()
        if FreeCAD.activeDocument().getObject("FCPlaneCdG"):
            self.parent.on_pushButton_ShowCdG()
        self.solid.ViewObject.ShapeColor=self.originColor
        defcolor = QtGui.QColor(255, 255, 255)
        self.spin.setStyleSheet('QDoubleSpinBox {background-color: %s}'%defcolor.name())


def convert_density(density_siunits, unit):
    """Convert the density in kg/m³ into another unit"""
    tu = FreeCAD.Units.parseQuantity
    return float(tu('{} kg/m^3'.format(density_siunits)) / tu(unit))


# This is the widget which does almost all of the work
# Widgets don't have close boxes, so closing is dealt with in
# CenterofmassWindow.
class CenterofmassWidget(QtGui.QWidget):
    def __init__(self, parent=None):
        super(CenterofmassWidget, self).__init__(parent)
        self.parent = parent
        self.solid_count = 0
        self.TotalCdG = [0, 0, 0]

    tu = FreeCAD.Units.parseQuantity

    material_database = {}

    # Lay out the interactive elements
    def initUI(self, parent):
        global g_win_width
        global sel

        check_Version()
        
        self.massTot = 0.0
        self.centerOfMass = [0.0, 0.0, 0.0]

        font = QtGui.QFont()
        font.setFamily('Times New Roman')
        font.setPointSize(10)
        font.setWeight(10)
        font.setBold(True)

        sel = FreeCADGui.Selection.getSelection()
        objs  = []
        self.solid_count = 0
        for s in range(len(sel)):
            if hasattr(sel[s], 'Shape'):
                if sel[s].Shape.Volume == 0:
                    error_dialog(u'invalid selection (select a solid or a mesh)')
                    self.destroy()
                else:
                    self.solid_count += 1
                    if sel[s].InList and sel[s].InList[0].TypeId == 'PartDesign::Body':
                        objs.append(sel[s].InList[0].Shape)
                    else:
                        objs.append(sel[s].Shape)
            elif hasattr(sel[s], 'Mesh'):
                if sel[s].Mesh.Volume == 0:
                    error_dialog(u'invalid selection (select a solid or a mesh)')
                    self.destroy()
                else:
                    self.solid_count += 1
                    objs.append(sel[s].Mesh)
            else:
                error_dialog(u'invalid selection (select a solid or a mesh)')
                self.destroy()

        if self.solid_count == 0:
            self.startup_failed = True
            FreeCAD.Console.PrintMessage(u'Select an object' + '\n')
            error_dialog(u'Select an object')
        else:
            self.startup_failed = False

        margin = 10

        self.setObjectName('CenterofmassWidget')

        self.label_MLU = QtGui.QLabel(self)
        self.label_MLU.setText('Density unit')

        self.comboUnit = QtGui.QComboBox(self)
        self.comboUnit.setToolTip('Unit of density')
        self.comboUnit.addItem('kg/m^3')
        self.comboUnit.addItem('g/dm^3')
        self.comboUnit.addItem('g/cm^3')
        self.comboUnit.addItem('g/mm^3')
        self.comboUnit.addItem('oz/in^3')
        self.comboUnit.addItem('lb/in^3')
        self.comboUnit.addItem('lb/ft^3')
        self.comboUnit.addItem('lb/yd^3')
        self.comboUnit.currentIndexChanged.connect(self.on_comboUnit_Changed)

        lengthU = self.comboUnit.currentText().split('/')[1].split('^')[0]
        massU = self.comboUnit.currentText().split('/')[0]

        self.materials = [0] * self.solid_count
        self.volumes = [0] * self.solid_count
        self.centerofmasses = [0] * self.solid_count
        self.masses = [0] * self.solid_count

        self.minBdX = 1e8
        self.minBdY = 1e8
        self.minBdZ = 1e8
        self.maxBdX = -1e8
        self.maxBdY = -1e8
        self.maxBdZ = -1e8

        layout = QtGui.QVBoxLayout(self)
        layout.setSpacing(0)        

        self.label_Title = QtGui.QLabel(self)
        self.label_Title.setObjectName('label_title')
        self.label_Title.setText('Density of selected solids      Default Density: ')
        
        self.defaultDensitySpin = QtGui.QDoubleSpinBox(self)
        self.defaultDensitySpin.setMinimum(1.0)
        self.defaultDensitySpin.setMaximum(25000.0)
        self.defaultDensitySpin.setValue(1000.0)
        self.defaultDensitySpin.setSingleStep(100)
        self.defaultDensitySpin.setDecimals(4)
        self.defaultDensitySpin.valueChanged.connect(self.on_defaultdensitySpinBox_valueChanged)
        self.defaultDensitySpin.setObjectName('doubleSpinBox_DefaultDensity')
        densityU = self.comboUnit.currentText()
        self.defaultDensitySpin.setToolTip('set default density (in ' + densityU + ')')
        
        self.allToDefaultDensityCheckBox = QtGui.QCheckBox(self)
        self.allToDefaultDensityCheckBox.setToolTip('set all solids to default density')
        self.allToDefaultDensityCheckBox.stateChanged.connect(self.setalltodefaultdensity_stateChanged)
        
        titleLayoutBox = QtGui.QGroupBox()
        titleLayout = QtGui.QHBoxLayout()
        titleLayout.addWidget(self.label_Title)
        titleLayout.addWidget(self.defaultDensitySpin)
        titleLayout.addWidget(self.allToDefaultDensityCheckBox)
        titleLayoutBox.setLayout(titleLayout)
        #titleLayoutBox.setFixedHeight(50)
        layout.addWidget(titleLayoutBox)        

        solidGroupBox = QtGui.QGroupBox()
        solidLayout = QtGui.QGridLayout()
        solidLayout.setVerticalSpacing(0)
        
        self.loadMaterials()
        
        for sol in range(self.solid_count):
            self.materials[sol] = MaterialWidget(
                label=QtGui.QLabel(self),
                spin=QtGui.QDoubleSpinBox(self),
                combo=QtGui.QComboBox(self),
                parent=self,
                material_database=self.material_database,
                solid = sel[sol],
                originColor = sel[sol].ViewObject.ShapeColor
            )

            self.materials[sol].label.setText(
                '{} : {}'.format(sol + 1, sel[sol].Label))


            self.materials[sol].spin.setMinimum(1.0)
            self.materials[sol].spin.setMaximum(25000.0)
            self.materials[sol].spin.setValue(1000.0)
            self.materials[sol].spin.setSingleStep(100)
            self.materials[sol].spin.setDecimals(4)
            self.materials[sol].spin.valueChanged.connect(self.materials[sol].on_densitySpinBox_valueChanged)
            self.materials[sol].spin.setObjectName('doubleSpinBox_density_%d' % sol)
            self.materials[sol].spin.setToolTip(
                'density of ' + sel[sol].Label + ' (in ' + self.comboUnit.currentText() +')')

            self.materials[sol].combo.addItem('custom')
            for m in sorted(self.material_database):
                self.materials[sol].combo.addItem(m)
            self.materials[sol].combo.setCurrentIndex(self.materials[sol].combo.findText('default'))
            self.materials[sol].combo.currentIndexChanged.connect(self.materials[sol].on_comboMaterial_Changed)

            self.volumes[sol] = objs[sol].Volume

            # Find the center of mass depending of the type of object.
            if hasattr(objs[sol], "CenterOfMass"):
                self.centerofmasses[sol] = objs[sol].CenterOfMass
            elif hasattr(objs[sol], "Solids"):
                self.centerofmasses[sol] = FreeCAD.Vector(0,0,0)
                for array_sol in objs[sol].Solids:
                    self.centerofmasses[sol] += array_sol.CenterOfMass
                self.centerofmasses[sol] /= objs[sol].Solids.__len__()
            #estimate cdg of a mesh
            elif hasattr(objs[sol],"Points"):
                self.centerofmasses[sol] = FreeCAD.Vector(0,0,0)
                for f in objs[sol].Facets:
                    currentVolume = (f.Points[0][0]*f.Points[1][1]*f.Points[2][2]
                        - f.Points[0][0]*f.Points[2][1]*f.Points[1][2]
                        - f.Points[1][0]*f.Points[0][1]*f.Points[2][2]
                        + f.Points[1][0]*f.Points[2][1]*f.Points[0][2]
                        + f.Points[2][0]*f.Points[0][1]*f.Points[1][2]
                        - f.Points[2][0]*f.Points[1][1]*f.Points[0][2]) / 6.
                    self.centerofmasses[sol][0] += ((f.Points[0][0] + f.Points[1][0] + f.Points[2][0]) / 4.) * currentVolume;
                    self.centerofmasses[sol][1] += ((f.Points[0][1] + f.Points[1][1] + f.Points[2][1]) / 4.) * currentVolume;
                    self.centerofmasses[sol][2] += ((f.Points[0][2] + f.Points[1][2] + f.Points[2][2]) / 4.) * currentVolume;

                self.centerofmasses[sol][0] /= self.volumes[sol]
                self.centerofmasses[sol][1] /= self.volumes[sol]
                self.centerofmasses[sol][2] /= self.volumes[sol]

            #2: an array is selected
            if hasattr(sel[sol], 'ArrayType'):
                if sel[sol].ArrayType == 'polar' and sel[sol].NumberPolar > 0:
                    self.centerofmasses[sol] = FreeCAD.Vector(0,0,0)
                    for array_sol in sel[sol].Shape.Solids:
                        self.centerofmasses[sol] += array_sol.CenterOfMass
                    self.centerofmasses[sol] /= sel[sol].Shape.Solids.__len__()
                else:
                    xvector = sel[sol].IntervalX
                    yvector = sel[sol].IntervalY
                    zvector = sel[sol].IntervalZ
                    if hasattr(sel[sol].Base, 'IfcRole'):
                        if sel[sol].Base.IfcRole == 'Reinforcing Bar':
                            axis = sel[sol].Base.Base.Placement.Rotation.multVec(FreeCAD.Vector(0, 0, -1))
                            if hasattr(sel[sol].Base, 'Direction'):
                                if not DraftVecUtils.isNull(sel[sol].Base.Direction):
                                    axis = sel[sol].Base.Direction
                                    axis.normalize()
                            self.centerofmasses[sol] += float(sel[sol].Base.Spacing) * axis * (float(sel[sol].Base.Amount - 1) / 2.)

                    for xcount in range(sel[sol].NumberX):
                        self.centerofmasses[sol] += xcount * xvector / (sel[sol].NumberX)
                    for ycount in range(sel[sol].NumberY):
                        self.centerofmasses[sol] += ycount * yvector / (sel[sol].NumberY)
                    for zcount in range(sel[sol].NumberZ):
                        self.centerofmasses[sol] += zcount * zvector / (sel[sol].NumberZ)

            if hasattr(sel[sol], 'IfcRole'):
                if sel[sol].IfcRole == 'Reinforcing Bar':
                    axis = sel[sol].Base.Placement.Rotation.multVec(FreeCAD.Vector(0, 0, -1))
                    if hasattr(sel[sol], 'Direction'):
                        if not DraftVecUtils.isNull(sel[sol].Direction):
                            axis = sel[sol].Direction
                            axis.normalize()
                    self.centerofmasses[sol] += float(sel[sol].Spacing) * axis * (float(sel[sol].Amount - 1) / 2.)
                
            if objs[sol].BoundBox.XMin < self.minBdX:
                self.minBdX = objs[sol].BoundBox.XMin
            if objs[sol].BoundBox.YMin < self.minBdY:
                self.minBdY = objs[sol].BoundBox.YMin
            if objs[sol].BoundBox.ZMin < self.minBdZ:
                self.minBdZ = objs[sol].BoundBox.ZMin
            if objs[sol].BoundBox.XMax > self.maxBdX:
                self.maxBdX = objs[sol].BoundBox.XMax
            if objs[sol].BoundBox.YMax > self.maxBdY:
                self.maxBdY = objs[sol].BoundBox.YMax
            if objs[sol].BoundBox.ZMax > self.maxBdZ:
                self.maxBdZ = objs[sol].BoundBox.ZMax
            
# translation for part containers
            for lis in sel[sol].InList:
                if hasattr(lis,'Placement'):
                    self.centerofmasses[sol] += lis.Placement.Base
                    if lis.Placement.Base[0]>0:
                        self.maxBdX += lis.Placement.Base[0]
                    if lis.Placement.Base[0]<0:
                        self.minBdX += lis.Placement.Base[0]
                    if lis.Placement.Base[1]>0:
                        self.maxBdY += lis.Placement.Base[1]
                    if lis.Placement.Base[1]<0:
                        self.minBdY += lis.Placement.Base[1]
                    if lis.Placement.Base[2]>0:
                        self.maxBdZ += lis.Placement.Base[2]
                    if lis.Placement.Base[2]<0:
                        self.minBdZ += lis.Placement.Base[2]                        
                        
            solidLayout.addWidget(self.materials[sol].label, sol, 0)
            solidLayout.addWidget(self.materials[sol].combo, sol, 1)
            solidLayout.addWidget(self.materials[sol].spin, sol, 2)

        solidGroupBox.setLayout(solidLayout)
        scroll = QtGui.QScrollArea()
        scroll.setWidget(solidGroupBox)
        #scroll.setWidgetResizable(True)
        layout.addWidget(scroll)

        macro_dir = FreeCAD.getUserMacroDir(True)
        icon_dir = os.path.join(macro_dir, "CenterOfMass/")
        self.setWindowIcon(QtGui.QIcon(icon_dir+'Macro_CenterOfMass.png'))

        self.calc = QtGui.QPushButton(self)
        self.calc.setObjectName('compute')
        self.calc.clicked.connect(self.on_pushButton_ComputeCDG)
        self.calc.setToolTip(u'compute centerOfMass')
        self.calc.setIcon(QtGui.QIcon(os.path.join(icon_dir, "Macro_CenterOfMass_compute.png")))
#        self.calc.setIconSize(QtCore.QSize(35, 35))
#        self.calc.setStyleSheet('QPushButton{border: 0px solid;}')

        self.export = QtGui.QPushButton(self)
        self.export.setEnabled(False)
        self.export.setObjectName('export')
        self.export.clicked.connect(self.on_pushButton_Export)
        self.export.setToolTip(u'export values to a .csv file')
        self.export.setIcon(QtGui.QIcon(os.path.join(icon_dir, "Macro_CenterOfMass_save.png")))
#        self.export.setIconSize(QtCore.QSize(35, 35))
#        self.export.setStyleSheet('QPushButton{border: 0px solid;}')

        self.readDensities = QtGui.QPushButton(self)
        self.readDensities.setObjectName('import')
        self.readDensities.clicked.connect(self.on_pushButton_Import)
        self.readDensities.setToolTip(u'import densities from a .csv file')
        self.readDensities.setIcon(QtGui.QIcon(os.path.join(icon_dir , "Macro_CenterOfMass_import.png")))
#        self.readDensities.setIconSize(QtCore.QSize(35, 35))
#        self.readDensities.setStyleSheet('QPushButton{border: 0px solid;}')

        self.editMat = QtGui.QPushButton(self)
        self.editMat.setObjectName('editMaterial')
        self.editMat.clicked.connect(self.on_pushButton_EditMat)
        self.editMat.setToolTip('Edit Material list')
        self.editMat.setIcon(QtGui.QIcon(os.path.join(icon_dir, "Macro_CenterOfMass_material.png")))
#        self.editMat.setIconSize(QtCore.QSize(35, 35))
#        self.editMat.setStyleSheet('QPushButton{border: 0px solid;}')

        buttonGroupBox = QtGui.QGroupBox()
        buttonLayout = QtGui.QHBoxLayout()
        buttonLayout.addWidget(self.calc)
        buttonLayout.addWidget(self.export)
        buttonLayout.addWidget(self.readDensities)
        buttonLayout.addWidget(self.editMat)
        buttonLayout.addWidget(self.label_MLU)
        buttonLayout.addWidget(self.comboUnit)
        buttonGroupBox.setLayout(buttonLayout)
        #buttonGroupBox.setFixedHeight(70)
        layout.addWidget(buttonGroupBox)

        self.label_Mass = QtGui.QLabel(self)
        self.label_Mass.setObjectName('label_Mass')
        self.label_Mass.setText('Total mass')
        self.resultMasseTot = QtGui.QLineEdit(self)
        self.resultMasseTot.setObjectName('total weight')
        self.resultMasseTot.setReadOnly(True)
        self.resultMasseTot.setPlaceholderText('no computation done')
        self.resultMasseTot.setToolTip('total weight (in {})'.format(massU))

        self.showCdg = QtGui.QPushButton(self)
        self.showCdg.setObjectName('showCdG')
        self.showCdg.clicked.connect(self.on_pushButton_ShowCdG)
        self.showCdg.setToolTip('show center of mass')
        self.showCdg.setEnabled(False)
        self.showCdg.setIcon(QtGui.QIcon(os.path.join(icon_dir, "Macro_CenterOfMass_com.png")))
#        self.showCdg.setIconSize(QtCore.QSize(30, 30))
        
        self.changeRadius = QtGui.QSlider(self)
        self.changeRadius.setObjectName('changeRadius')
        self.changeRadius.valueChanged.connect(self.on_slideButton_changeRadius)
        self.changeRadius.setToolTip('change radius of spheres')
#        self.changeRadius.setFixedWidth(25)
        self.changeRadius.setEnabled(False)
        self.changeRadius.setMaximum(49)

        self.colorify = QtGui.QPushButton(self)
        self.colorify.setObjectName('colorify')
        self.colorify.clicked.connect(self.on_pushButton_Colorify)
        self.colorify.setToolTip('colorify shapes')
        self.colorify.setEnabled(False)
        self.colorify.setIcon(QtGui.QIcon(os.path.join(icon_dir, "Macro_CenterOfMass_colorify.png")))
#        self.colorify.setIconSize(QtCore.QSize(30, 30))

        massGroupBox = QtGui.QGroupBox()
        massLayout = QtGui.QHBoxLayout()
        massLayout.addWidget(self.label_Mass)
        massLayout.addWidget(self.resultMasseTot)
        massLayout.addWidget(self.showCdg)
        massLayout.addWidget(self.changeRadius)
        massLayout.addWidget(self.colorify)
        massGroupBox.setLayout(massLayout)
       # massGroupBox.setFixedHeight(50)
        layout.addWidget(massGroupBox)

        self.label_CdG = QtGui.QLabel(self)
        self.label_CdG.setObjectName('label_CdG')
        self.label_CdG.setText('Center of mass')
        self.resultCdGX = QtGui.QLineEdit(self)
#        self.resultCdGX.setGeometry(QtCore.QRect(115, g_win_height - margin - 30, 65, 25))
        self.resultCdGX.setObjectName('center of mass')
        self.resultCdGX.setReadOnly(True)
        self.resultCdGX.setPlaceholderText('no computation done')
        self.resultCdGX.setToolTip('center of mass X (in %s)' % lengthU)

        self.resultCdGY = QtGui.QLineEdit(self)
        self.resultCdGY.setObjectName('center of mass')
        self.resultCdGY.setReadOnly(True)
        self.resultCdGY.setPlaceholderText('no computation done')
        self.resultCdGY.setToolTip('center of mass Y (in %s)' % lengthU)

        self.resultCdGZ = QtGui.QLineEdit(self)
        self.resultCdGZ.setObjectName('center of mass')
        self.resultCdGZ.setReadOnly(True)
        self.resultCdGZ.setPlaceholderText('no computation done')
        self.resultCdGZ.setToolTip('center of mass Z (in %s)' % lengthU)

        cdgGroupBox = QtGui.QGroupBox()
        cdgLayout = QtGui.QHBoxLayout()
        cdgLayout.addWidget(self.label_CdG)
        cdgLayout.addWidget(self.resultCdGX)
        cdgLayout.addWidget(self.resultCdGY)
        cdgLayout.addWidget(self.resultCdGZ)
        cdgGroupBox.setLayout(cdgLayout)
        #cdgGroupBox.setFixedHeight(50)
        layout.addWidget(cdgGroupBox)

    def on_pushButton_EditMat(self):
        MaterialEditor.openEditor()
        self.loadMaterials()
        for sol in range(self.solid_count):
            for m in sorted(self.material_database):
                if self.materials[sol].combo.findText(m) == -1:
                    self.materials[sol].combo.addItem(m)

    def getMaterialResources(self):
        self.fem_prefs = FreeCAD.ParamGet("User parameter:BaseApp/Preferences/Mod/Material/Resources")
        use_built_in_materials = self.fem_prefs.GetBool("UseBuiltInMaterials", True)
        use_mat_from_config_dir = self.fem_prefs.GetBool("UseMaterialsFromConfigDir", True)
        use_mat_from_custom_dir = self.fem_prefs.GetBool("UseMaterialsFromCustomDir", True)
        if use_mat_from_custom_dir:
            custom_mat_dir = self.fem_prefs.GetString("CustomMaterialsDir", "")
        # later found cards with same name will override cards
        # FreeCAD returns paths with / at the end, thus not os.sep is needed on first +
        self.resources = []
        if use_built_in_materials:
            self.resources.append(FreeCAD.getResourceDir() + "Mod" + os.sep + "Material" + os.sep + "StandardMaterial")
        if use_mat_from_config_dir:
            self.resources.append(FreeCAD.ConfigGet("UserAppData") + "Material")
        if use_mat_from_custom_dir:
            custom_mat_dir = self.fem_prefs.GetString("CustomMaterialsDir", "")
            if os.path.exists(custom_mat_dir):
                self.resources.append(custom_mat_dir)
        self.outputResources()

    def outputResources(self):
        print('locations to look for material cards:')
        for path in self.resources:
            print('  ' + path)
        print('\n')

    def loadMaterials(self):
        self.getMaterialResources()
        materials_cards = {}
        for p in self.resources:
            if os.path.exists(p):
                for f in sorted(os.listdir(p)):
                    b, e = os.path.splitext(f)
                    if e.upper() == ".FCMAT":
                        materials_cards[b] = p + os.sep + f

        for mat_card in sorted(materials_cards):
            tu = FreeCAD.Units.parseQuantity
            self.material_database['default'] = float(tu('{}'.format(self.defaultDensitySpin.value())+self.comboUnit.currentText()) / tu('kg/m^3'))

            import importFCMat
            try :
                d = importFCMat.read(materials_cards[mat_card])
                self.material_database[mat_card] = float(d.get('Density').split(' ')[0])
            except:
                pass

    def convertLength(self, length):
        length_unit = self.comboUnit.currentText().split('/')[1].split('^')[0]
        return float(self.tu('{} mm'.format(length)) / self.tu(length_unit))

    def convertVolume(self, volume):
        densityU = self.comboUnit.currentText()
        volU = densityU.split('/')[1]
        volumeConverted = float(self.tu('%f mm^3' % volume) / self.tu(volU))
        return volumeConverted

    def on_defaultdensitySpinBox_valueChanged(self, defDensity):
        tu = FreeCAD.Units.parseQuantity
        if defDensity<self.defaultDensitySpin.maximum() and defDensity>self.defaultDensitySpin.minimum():
            self.material_database['default'] = float(tu('{}'.format(defDensity)+self.comboUnit.currentText()) / tu('kg/m^3'))
    
    def setalltodefaultdensity_stateChanged(self, state):
        for sol in range(self.solid_count):
            self.materials[sol].combo.setCurrentIndex(0)
            self.materials[sol].combo.setCurrentText('default');                    
        self.allToDefaultDensityCheckBox.setChecked(False)
        
    def on_comboUnit_Changed(self, txt):
        densityU = self.comboUnit.currentText()
        lengthU = densityU.split('/')[1].split('^')[0]
        massU = densityU.split('/')[0]
        self.resultMasseTot.setToolTip('total weight (in %s)' % massU)
        self.resultCdGX.setToolTip('center of mass X (in %s)' % lengthU)
        self.resultCdGY.setToolTip('center of mass Y (in %s)' % lengthU)
        self.resultCdGZ.setToolTip('center of mass Z (in %s)' % lengthU)
        for sol in range(self.solid_count):
            self.materials[sol].spin.setToolTip('density of ' + sel[sol].Label + ' (in ' + densityU + ')')
            prevMaterial = self.materials[sol].combo.currentIndex()
            self.materials[sol].spin.setMinimum(convert_density(1, densityU))
            self.materials[sol].spin.setMaximum(convert_density(25000, densityU))
            self.materials[sol].spin.setSingleStep(convert_density(100, densityU))
            self.materials[sol].combo.setCurrentIndex(0)
            self.materials[sol].combo.setCurrentIndex(prevMaterial)
        
        prevDensity = self.defaultDensitySpin.value()
        self.defaultDensitySpin.setToolTip('default density (in ' + densityU + ')')
        self.defaultDensitySpin.setSingleStep(convert_density(100, densityU))
        self.defaultDensitySpin.setMinimum(0)
        self.defaultDensitySpin.setMaximum(1e10)
        self.defaultDensitySpin.setValue(convert_density(self.material_database.get('default', -10.0), densityU))
        self.defaultDensitySpin.setMinimum(convert_density(1, densityU))
        self.defaultDensitySpin.setMaximum(convert_density(25000, densityU))        
        
        self.on_pushButton_ComputeCDG()

    def on_pushButton_ComputeCDG(self):
        self.massTot = 0
        self.volTot = 0
        self.TotalCdG=FreeCAD.Vector(0,0,0)
        for sol in range(self.solid_count):
            volumeInUnit = self.convertVolume(self.volumes[sol])
            self.masses[sol] = volumeInUnit * self.materials[sol].spin.value()
            self.massTot += self.masses[sol]
            self.volTot += volumeInUnit
        for sol in range(self.solid_count):
            self.TotalCdG += 1 / self.massTot * self.masses[sol] * self.centerofmasses[sol]
        self.resultMasseTot.setText('{:.6}'.format(self.massTot))
        self.resultCdGX.setText('{:.4}'.format(self.convertLength(self.TotalCdG[0])))
        self.resultCdGY.setText('{:.4}'.format(self.convertLength(self.TotalCdG[1])))
        self.resultCdGZ.setText('{:.4}'.format(self.convertLength(self.TotalCdG[2])))

        self.export.setEnabled(True)
        self.showCdg.setEnabled(True)
        self.colorify.setEnabled(True)

    def on_slideButton_changeRadius(self):
        self.on_pushButton_ShowCdG()
        
    def on_pushButton_Colorify(self):
        import colorsys
        for sol in range(self.solid_count):
            density = self.materials[sol].spin.value()
            densityU = self.comboUnit.currentText()
            densityConverted = float(self.tu('%f %s' % (density, densityU)) / self.tu('kg/m^3'))
            dThous = densityConverted // 1000.
            dHund = (densityConverted - dThous*1000.) // 100.
            dTen = (densityConverted - dThous*1000 - dHund*100) // 10
            maxD = 21000.
            h = densityConverted/maxD
            s = 1. - 0.5*(dHund/10.)
            v = 1. - 0.5*(dTen/10.)
            rgb = colorsys.hsv_to_rgb(h, s, v)
            FreeCAD.ActiveDocument.getObject(sel[sol].Name).ViewObject.ShapeColor=(rgb)
            color = QtGui.QColor(int(rgb[0]*255.), int(rgb[1]*255.), int(rgb[2]*255.))
            self.materials[sol].spin.setStyleSheet('QDoubleSpinBox {background-color: %s}'%color.name())

    def on_pushButton_ShowCdG(self):
        doc = FreeCAD.activeDocument()
        try:
            doc.getObject("FCPlaneCdG").removeObjectsFromDocument()
            doc.removeObject("FCPlaneCdG")
        except Exception:
            None

        boundBoxLX  = self.maxBdX - self.minBdX
        boundBoxLY  = self.maxBdY - self.minBdY
        boundBoxLZ  = self.maxBdZ - self.minBdZ
        FCSpring = doc.addObject('App::DocumentObjectGroup', 'FCPlane' + 'CdG')
        plr = FreeCAD.Placement()
        plr.Base = FreeCAD.Vector(self.TotalCdG[0], self.TotalCdG[1], self.TotalCdG[2])

        #Sphere to represent the center of masses
        radiusCOM = (1+self.changeRadius.value())/100.
        sphere = FreeCAD.ActiveDocument.addObject('Part::Sphere', 'CenterOfMass')
        sphere.Placement = plr
        sphere.Radius = radiusCOM * (max(boundBoxLX, max(boundBoxLY, boundBoxLZ)))
        sphere.ViewObject.ShapeColor = (0.6, 0.0, 0.0)
        sphere.ViewObject.Transparency = 5
        sphere.ViewObject.LineWidth = 1.0
        FCSpring.addObject(sphere)

        if self.solid_count > 1:
            for sol in range(self.solid_count):
                sphere = FreeCAD.ActiveDocument.addObject('Part::Sphere', 'CenterOfMass_' + sel[sol].Label)
                plrSol = FreeCAD.Placement()
                plrSol.Base = FreeCAD.Vector(self.centerofmasses[sol][0],
                                         self.centerofmasses[sol][1],
                                         self.centerofmasses[sol][2])
                sphere.Placement = plrSol
                sphere.Radius = radiusCOM * (max(boundBoxLX, max(boundBoxLY, boundBoxLZ)))*math.pow(self.masses[sol]/self.massTot, 1./3.)
                sphere.ViewObject.ShapeColor = (0.0, 0.6, 0.0)
                sphere.ViewObject.Transparency = 5
                sphere.ViewObject.LineWidth = 1.0
                FCSpring.addObject(sphere)

        ### PlaneYZ
        plan = FreeCAD.ActiveDocument.addObject('Part::Plane', 'PlaneYZ')
        plan.Length = boundBoxLZ
        plan.Width = boundBoxLY
        plp = FreeCAD.Placement()
        plp.Base = FreeCAD.Vector(self.TotalCdG[0], self.TotalCdG[1]-boundBoxLY/2., self.TotalCdG[2] - boundBoxLZ/2.)
        plan.Placement = plp
        plan.Placement.Rotation = plan.Placement.Rotation.multiply(FreeCAD.Rotation(0.0, -90.0, 0.0))
        plan.Placement.Base.x = self.TotalCdG[0]        
        plan.Placement.Base.y = self.minBdY
        plan.Placement.Base.z = self.minBdZ

        plan.ViewObject.LineColor = (1.0, 0.66667, 0.0)
        plan.ViewObject.ShapeColor = (0.6, 0.0, 0.0)
        plan.ViewObject.Transparency = 90
        plan.ViewObject.LineWidth = 1.0
        FCSpring.addObject(plan)
        ### PlaneXZ
        plan = FreeCAD.ActiveDocument.addObject('Part::Plane', 'PlaneXZ')
        plan.Length = boundBoxLX
        plan.Width = boundBoxLZ
        plp.Base = FreeCAD.Vector(self.TotalCdG[0]-boundBoxLX/2., self.TotalCdG[1], self.TotalCdG[2]-boundBoxLZ/2.)
        plan.Placement = plp
        plan.Placement.Rotation = plan.Placement.Rotation.multiply(FreeCAD.Rotation(0.0, 0.0, 90.0))
        plan.Placement.Base.x = self.minBdX      
        plan.Placement.Base.y = self.TotalCdG[1]  
        plan.Placement.Base.z = self.minBdZ

        plan.ViewObject.LineColor = (1.0, 0.66667, 0.0)
        plan.ViewObject.ShapeColor = (0.0, 0.6, 0.0)
        plan.ViewObject.Transparency = 90
        plan.ViewObject.LineWidth = 1.0
        FCSpring.addObject(plan)
        ### PlaneXY
        plan = FreeCAD.ActiveDocument.addObject('Part::Plane', 'PlaneXY')
        plan.Length = boundBoxLX
        plan.Width = boundBoxLY
        plp.Base = FreeCAD.Vector(self.TotalCdG[0] - boundBoxLX/2., self.TotalCdG[1] - boundBoxLY/2., self.TotalCdG[2])
        plan.Placement = plp
        plan.Placement.Base.x = self.minBdX
        plan.Placement.Base.y = self.minBdY
        plan.Placement.Base.z = self.TotalCdG[2]

        plan.ViewObject.LineColor = (1.0, 0.66667, 0.0)
        plan.ViewObject.ShapeColor = (0.0, 0.0, 0.6)
        plan.ViewObject.Transparency = 90
        plan.ViewObject.LineWidth = 1.0
        FCSpring.addObject(plan)
        ### BoundingBox
        plr = FreeCAD.Placement()
        plr.Base = FreeCAD.Vector( self.minBdX, self.minBdY, self.minBdZ)
        BBoxSolid = FreeCAD.ActiveDocument.addObject("Part::Box","BBoxSolid")
        BBoxSolid.Placement.Base = plr.Base
        BBoxSolid.Label = "BBoxSolid"
        BBoxSolid.Length = boundBoxLX
        BBoxSolid.Width  = boundBoxLY
        BBoxSolid.Height = boundBoxLZ
        BBoxSolid.ViewObject.ShapeColor = (0.5, 0.5, 0.5)
        BBoxSolid.ViewObject.Transparency = 90
        FCSpring.addObject(BBoxSolid)

        doc.recompute()
        
        self.changeRadius.setEnabled(True)

    def on_pushButton_Export(self):
        SaveName = ''
        SaveName, Filter = QtGui.QFileDialog.getSaveFileName(
            None,
            'Save a file .csv',
            os.path.expanduser('~'),
            '*.csv *.txt;Cvs (*.csv);;TXT (*.txt)')
        if SaveName == '':
            FreeCAD.Console.PrintMessage('Saving file canceled' + '\n')
            error_dialog('saving file canceled')
        else:
            FreeCAD.Console.PrintMessage('Saving ' + SaveName + '\n')

            try:
                if sys.version_info.major >= 3:
                    f = open(SaveName, 'w', encoding="utf-8") # write
                else:
                    f = open(SaveName, 'w') # write

                densityU = self.comboUnit.currentText()
                volU = densityU.split('/')[1]
                lengthU = densityU.split('/')[1].split('^')[0]
                massU = densityU.split('/')[0]

                f.write('Number\tLabel\tMaterial\tVolume (%s)\tDensity (%s)\tWeight (%s)\tCenter of mass X (%s)\tCenter of mass Y (%s)\tCenter of mass Z (%s)\n' % (
                    volU, densityU, massU, lengthU, lengthU, lengthU))
                for sol in range(self.solid_count):
                    objectName = sel[sol].Label
                    f.write('%d\t%s\t%s\t%.6e\t%.6e\t%.6e\t%.6e\t%.6e\t%.6e\n' % (
                        sol + 1, sel[sol].Label, self.materials[sol].combo.currentText(),
                        self.convertVolume(self.volumes[sol]),
                        self.materials[sol].spin.value(), self.masses[sol],
                        self.convertLength(self.centerofmasses[sol][0]),
                        self.convertLength(self.centerofmasses[sol][1]),
                        self.convertLength(self.centerofmasses[sol][2])))

                f.write('\nTotal\t\t\t%.6e\t%.6e\t%.6e\t%.6e\t%.6e\t%.6e\n' % (
                    self.volTot,
                    self.massTot/self.volTot,
                    self.massTot,
                    self.convertLength(self.TotalCdG[0]),
                    self.convertLength(self.TotalCdG[1]),
                    self.convertLength(self.TotalCdG[2])))
                f.close()
                FreeCAD.Console.PrintMessage(SaveName + ' saved\n')

            except Exception:
                FreeCAD.Console.PrintMessage('Error writing file ' + SaveName + '\n')
                error_dialog('Error writing file ' + SaveName)

    def on_pushButton_Import(self):
        filename, filter = QtGui.QFileDialog.getOpenFileName(
            parent=self,
            caption='Open file',
            filter='*.csv')

        if filename == "":
            FreeCAD.Console.PrintMessage('importing file canceled' + '\n')
            error_dialog('importing file canceled')
        else:
            FreeCAD.Console.PrintMessage('reading densities from %s\n' % filename)
        # open csv file
            if sys.version_info.major >= 3:
                csvfile = open(filename, 'r', encoding='utf-8')
                reader = csv.DictReader(csvfile, delimiter='\t')
            else:
                csvfile = open(filename, 'r')
                reader = csv.DictReader(csvfile, delimiter=str('\t').encode('utf-8'))

            densityUnits = ['', ' (kg/m^3)', ' (g/dm^3)', ' (g/cm^3)', 'g/mm^3', ' (oz/in^3)', ' (lb/in^3)', ' (lb/ft^3)',
                                ' (lb/yd^3)']

            selList = [0] * self.solid_count
            for s in range(self.solid_count):
                selList[s] = sel[s].Label

            matLoaded = 0
            for row in reader:
                if matLoaded < self.solid_count:
                    if row['Label'] in selList:
                        selPosition = selList.index(row['Label'])
                        try:
                            self.materials[selPosition].combo.setCurrentIndex(
                                self.materials[selPosition].combo.findText(row['Material']))
                        except:
                            FreeCAD.Console.PrintWarning('Unknown material or unable to find a "Material" column in the file --> Material set to "custom"')
                            self.materials[selPosition].combo.setCurrentIndex(
                                self.materials[selPosition].combo.findText('custom'))
                    else:
                        FreeCAD.Console.PrintWarning('Name label in the .csv file does not fit any selected shape --> Material keep to "default"')

                    if self.materials[selPosition].combo.currentText() == 'custom':
                        try:
                            for u in range(len(densityUnits)):
                                try:
                                    self.materials[selPosition].spin.setValue(float(row['Density' + densityUnits[u]]))
                                except:
                                    pass

                        except:
                            self.materials[selPosition].combo.setCurrentIndex(
                                self.materials[selPosition].combo.findText('default'))
                            FreeCAD.Console.PrintWarning('Unable to find a "Density" column in the file --> Material set to "default"')
                    matLoaded += 1

def check_Version():
    urlRaw='https://raw.githubusercontent.com/chupins/FreeCAD-macros/SC_Branch/Information/CenterOfMass.FCMacro'
    
    import re, sys
    resp_ok = False
    if (sys.version_info > (3, 0)):  #py3
        import urllib
        from urllib import request, error #URLError, HTTPError
        req = request.Request(urlRaw)
        try:
            response = request.urlopen(req)
            resp_ok = True
            the_page = response.read().decode("utf-8")
        except error.HTTPError as e:
            FreeCAD.Console.PrintWarning('The server couldn\'t fulfill the request.')
            FreeCAD.Console.PrintWarning('Error code: ' + str(e.code)+'\n')
        except error.URLError as e:
            FreeCAD.Console.PrintWarning('We failed to reach a server.\n')
            FreeCAD.Console.PrintWarning('Reason: '+ str(e.reason)+'\n')

    else:  #py2
        import urllib2
        from urllib2 import Request, urlopen, URLError, HTTPError
        req = Request(urlRaw)
        try:
            response = urlopen(req)
            resp_ok = True
            the_page = response.read()
        except HTTPError as e:
            FreeCAD.Console.PrintWarning('The server couldn\'t fulfill the request.')
            FreeCAD.Console.PrintWarning('Error code: ' + str(e.code)+'\n')
        except URLError as e:
            FreeCAD.Console.PrintWarning('We failed to reach a server.\n')
            FreeCAD.Console.PrintWarning('Reason: '+ str(e.reason)+'\n')        
            
    if resp_ok:
        pos=the_page.find('__Version__')   
        onlineVersion=(the_page[pos+15:pos+20])
        pos=the_page.find('__Date__')   
        onlineDate=(the_page[pos+12:pos+22])

        delta_Version = cmpVersion(__Version__, onlineVersion)
        if delta_Version > 0:
            FreeCAD.Console.PrintMessage('local version is ahead online version\n\tonline '+onlineVersion+'('+onlineDate+')\n\tlocal '+__Version__+'('+__Date__+')\n')
        elif delta_Version < 0:
            FreeCAD.Console.PrintError('PLEASE UPDATE "Center Of Mass" Macro.\n')
            msg="""
            <font color=red>PLEASE UPDATE "Center Of Mass" Macro.</font>
            <br>through \"Tools\" --> \"Addon manager\" Menu
            <br><br><b>your release is """+__Version__+""" ("""+__Date__+""")</b>
            <br><b>last release is """+onlineVersion+""" ("""+onlineDate+""")</b>
            """
            QtGui.QApplication.restoreOverrideCursor()
            reply = QtGui.QMessageBox.information(None,"Warning", msg)                   
        else:
            FreeCAD.Console.PrintMessage('the macro is Up to Date\n')

def cmp(a,b):
    return ((a>b)-(a<b))

def cmpVersion(version1, version2):
    def normalize(v):
        return [int(x) for x in re.sub(r'(\.0+)*$','', v).split(".")]
    return cmp(normalize(version1), normalize(version2))

def error_dialog(msg):
    diag = QtGui.QMessageBox(QtGui.QMessageBox.Critical, 'Error Message', msg)
    diag.setWindowFlags(QtCore.Qt.WindowStaysOnTopHint)
    diag.exec_()

# Create the window and start it
myWidget = CenterofmassWindow()

#myWidget = CenterofmassWidget()
#myWidget.initUI(myWidget)
#myNewFreeCADWidget = QtGui.QDockWidget()     # create a new dockwidget
#g_freecad_root_window.addDockWidget(QtCore.Qt.RightDockWidgetArea, myWidget)
